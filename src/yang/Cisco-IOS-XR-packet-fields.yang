module Cisco-IOS-XR-packet-fields {
	namespace "http://cisco.com/ns/yang/Cisco-IOS-XR-packet-fields";
  prefix pf;
  
  import ietf-inet-types {
    prefix inet;
  }
  
  import ietf-yang-types {
    prefix yang;
  }
  
  import ietf-ethertype {
    prefix et;
  }

  organization 
    "Cisco Systems, Inc.";
  
  contact
    "Cisco Systems, Inc.
     Customer Service

     Postal: 170 W Tasman Drive
     San Jose, CA 95134

     Tel: +1 1800 553-NETS

     E-mail: cs-yang@cisco.com";

  description
    "This YANG module defines groupings that are used by
     Cisco-IOS-XR-acl YANG module. Their usage is not
     limited to Cisco-IOS-XR-acl and can be
     used anywhere as applicable, such as QoS match criteria.
	  
     Copyright (c) 2013-2017 by Cisco Systems, Inc.
     All rights reserved.";
  
  revision YYYY-MM-DD {
    description
      "Inital version.";
    reference
      "Cisco Packet Fields module.";
  }
  
  /*
   * Typedefs
   */
  typedef operator {
    type enumeration {
      enum lt {
        description
          "Less than.";
      }
      enum lte {
        description
          "Less than or equal.";
      }
      enum gt {
        description
          "Greater than.";
      }
      enum gte {
        description
          "Greater than or equal.";
      }
      enum eq {
        description
          "Equal to.";
      }
      enum neq {
        description
          "Not equal to.";
      }
    }
    description
      "The source and destination port range definitions
       can be further qualified using an operator. An
       operator is needed only if lower-port is specified
       and upper-port is not specified. The operator
       therefore further qualifies lower-port only.";
  }
  
  grouping port {
    leaf lower-port {
      mandatory true;
      type union {
        type enumeration {
    	  enum any {
    	    description
    	      "Any valid port number.";
          }
        }
        type inet:port-number;
      }
      description
        "Lower boundary for port.";
    }
    leaf upper-port {
      must ". >= ../lower-port" {
        error-message
          "The upper-port must be greater than or equal 
           to lower-port";
      }
      description
        "Upper boundary for port. If it exists, the upper port
         must be greater or equal to lower-port.";
      
      type union {
        type enumeration {
          enum any {
            description
              "Any valid port number.";
          }
        }
        type inet:port-number;
      }
    }
    leaf operation {
      type operator;
      must "(lower-port and not(upper-port))" {
        error-message
          "If lower-port is specified, and an operator is also
           specified, then upper-port should not be specified.";
        description
          "If lower-port is specified, and an operator is also
           specified, then upper-port should not be specified.";
      }
      default eq;
      description
        "Operator to be applied on the lower-port.";
    }
  }
  
  grouping transport-header {
    description
      "Transport header fields";
    container source-port {
      presence "Enables setting source port range";
      description
        "Inclusive range representing source ports to be used.
    	 When only lower-port is present, it represents a single 
         port and eq operator is assumed to be default.
          
         When both lower-port and upper-port are specified,
         it implies a range inclusive of both values.";
      uses port;
    }
    
    container destination-port {
      presence "Enables setting destination port range";
      description
        "Inclusive range representing destination ports to be used. 
         When only lower-port is present, it represents a single 
         port and eq operator is assumed to be default.
         
         When both lower-port and upper-port are specified,
         it implies a range inclusive of both values ";
      uses port;
    }
  }
  
  grouping ip-header {
    description
      "IP header fields common to ipv4 and ipv6";
    reference
      "RFC 791.";
    
    leaf dscp {
      type inet:dscp;
    }
    
    leaf ecn {
      type uint8 {
        range 0..3;
      }
      description
        "Explicit Congestion Notification.";
      reference
        "RFC 3168.";
    }
    
    leaf length {
      type uint16;
      description
        "In IPv4 header field, this field is known as the Total Length.
         Total Length is the length of the datagram, measured in octets,
         including internet header and data.
    	  
         In IPv6 header field, this field is known as the Payload 
         Length, the length of the IPv6 payload, i.e. the rest of 
         the packet following the IPv6 header, in octets.";
      reference
        "RFC 719, RFC 2460";
    }

    leaf ttl {
      type uint8;
      description
        "This field indicates the maximum time the datagram is allowed 
         to remain in the internet system.  If this field contains the 
         value zero, then the datagram must be destroyed.
    	  
         In IPv6, this field is known as the Hop Limit.";
      reference "RFC 719, RFC 2460";
    }
    
    leaf protocol {
      type uint8;
      description
        "Internet Protocol number.";
    }
    uses transport-header;
  }
  
  grouping ipv4-header {
    description
      "Fields in IPv4 header.";
    
    leaf ihl {
      type uint8 {
        range "5..60";
      }
      description
        "An IPv4 header field, the Internet Header Length (IHL) is 
    	 the length of the internet header in 32 bit words, and 
         thus points to the beginning of the data. Note that the 
         minimum value for a correct header is 5.";
    }
    
    leaf flags {
      type bits {
        bit reserved {
          position 0;
          description
            "Reserved. Must be zero.";
        }
        bit fragment {
          position 1;
          description
            "Setting value to 0 indicates may fragment, while setting
             the value to 1 indicates do not fragment.";
        }
        bit more {
          position 2;
          description
            "Setting the value to 0 indicates this is the last fragment,
             and setting the value to 1 indicates more fragments are 
             coming.";
        }
      }
      description
        "Bit definitions for the flags field in IPv4 header.";
    }
    
    leaf offset {
      type uint16 {
        range "20..65535";
      }
      description
        "The fragment offset is measured in units of 8 octets (64 bits).  
         The first fragment has offset zero. The length is 13 bits";
    }
    
    leaf identification {
      type uint16;
      description
        "An identifying value assigned by the sender to aid in 
         assembling the fragments of a datagram.";
    }
    
    leaf ipv4-destination-address {
      type inet:ipv4-prefix;
      description
        "Destination IPv4 address prefix.";
    }
    leaf ipv4-source-address {
      type inet:ipv4-prefix;
      description
        "Source IPv4 address prefix.";
    }
  }
  
  grouping ipv6-header {
    description
      "Fields in IPv6 header";
    
    leaf next-header {
      type uint8;
      description
        "Identifies the type of header immediately following the 
         IPv6 header. Uses the same values as the IPv4 Protocol 
         field.";
      reference
        "RFC 2460";
    }
    
    leaf ipv6-destination-address {
      type inet:ipv6-prefix;
      description
        "Destination IPv6 address prefix.";
    }
    
    leaf destination-flow-label {
      type inet:ipv6-flow-label;
      description
        "Destination IPv6 Flow label.";
    }
    
    leaf ipv6-source-address {
      type inet:ipv6-prefix;
      description
        "Source IPv6 address prefix.";
    }
    
    leaf source-flow-label {
      type inet:ipv6-flow-label;
      description
        "Destination IPv6 Flow label.";
    }
    
    reference
      "RFC 4291: IP Version 6 Addressing Architecture
       RFC 4007: IPv6 Scoped Address Architecture
       RFC 5952: A Recommendation for IPv6 Address Text 
                 Representation";
  }
  
  grouping ethernet-header {
    description
      "Fields in Ethernet header.";
    
    leaf destination-mac-address {
      type yang:mac-address;
      description
        "Destination IEEE 802 MAC address.";
    }
    leaf destination-mac-address-mask {
      type yang:mac-address;
      description
        "Destination IEEE 802 MAC address mask.";
    }
    leaf source-mac-address {
      type yang:mac-address;
      description
        "Source IEEE 802 MAC address.";
    }
    leaf source-mac-address-mask {
      type yang:mac-address;
      description
        "Source IEEE 802 MAC address mask.";
    }
    leaf ethertype {
      type et:ethertype;
    }
  }
  
  grouping tcp-header {
    description
      "Collection of TCP header fields that can be used to 
       setup a match filter.";

    leaf sequence-number {
      type uint32;
      description
        "Sequence number that appears in the packet.";
    }
	
    leaf acknowledgement-number {
      type uint32;
      description
        "The acknowledgement number that appears in the 
         packet.";
    }
	
    leaf data-offset {
      type uint8 {
        range "5..15";
      }
      description
        "Specifies the size of the TCP header in 32-bit 
         words. The minimum size header is 5 words and 
         the maximum is 15 words thus giving the minimum 
         size of 20 bytes and maximum of 60 bytes, 
         allowing for up to 40 bytes of options in the 
         header.";
    }
	
    leaf reserved {
      type uint8;
      description
        "Reserved for future use.";
    }
	
    leaf flags {
      type bits {
        bit ns {
          position 0;
          description
            "ECN-nonce concealment protection";
          reference "RFC 3540).";
        }
        bit cwr {
          position 1;
          description
            "Congestion Window Reduced (CWR) flag is set by 
             the sending host to indicate that it received 
             a TCP segment with the ECE flag set and had 
             responded in congestion control mechanism.";
          reference "RFC 3168";
        }
        bit ece {
          position 2;
          description
            "ECN-Echo has a dual role, depending on the value 
             of the SYN flag. It indicates:
             If the SYN flag is set (1), that the TCP peer is ECN 
             capable. If the SYN flag is clear (0), that a packet 
             with Congestion Experienced flag set (ECN=11) in IP 
             header was received during normal transmission 
             (added to header by RFC 3168). This serves as an 
             indication of network congestion (or impending 
             congestion) to the TCP sender.";
        }
        bit urg {
          position 3;
          description
            "Indicates that the Urgent pointer field is significant.";
        }
        bit ack {
          position 4;
          description
            "Indicates that the Acknowledgment field is significant. 
             All packets after the initial SYN packet sent by the 
             client should have this flag set.";
        }
        bit psh {
          position 5;
          description
            "Push function. Asks to push the buffered data to the 
             receiving application.";
        }
        bit rst {
          position 6;
          description
            "Reset the connection.";
        }
        bit syn {
          position 7;
          description
            "Synchronize sequence numbers. Only the first packet 
             sent from each end should have this flag set. Some 
             other flags and fields change meaning based on this 
             flag, and some are only valid for when it is set, 
             and others when it is clear.";
        }
        bit fin {
          position 8;
          description
            "Last package from sender.";
        }
      }
      description
        "Also known as Control Bits. Contains 9 1-bit flags.";
    }
	
    leaf window-size {
      type uint16;
      description
        "The size of the receive window, which specifies 
         the number of window size units (by default, 
         bytes) (beyond the segment identified by the 
         sequence number in the acknowledgment field) 
         that the sender of this segment is currently 
         willing to receive.";
    }
	
    leaf urgent-pointer {
      type uint16;
      description
        "This field is an offset from the sequence number
         indicating the last urgent data byte.";
    }
	
    leaf options {
      type uint32;
      description
        "The length of this field is determined by the 
         data offset field. Options have up to three 
         fields: Option-Kind (1 byte), Option-Length 
         (1 byte), Option-Data (variable). The Option-Kind 
         field indicates the type of option, and is the 
         only field that is not optional. Depending on 
         what kind of option we are dealing with, 
         the next two fields may be set: the Option-Length 
         field indicates the total length of the option, 
         and the Option-Data field contains the value of 
         the option, if applicable.";
    }
  }
  
  grouping udp-header {
    description
      "Collection of UDP header fields that can be used 
       to setup a match filter.";
    
    leaf length {
      type uint16;
      description
        "A field that specifies the length in bytes of 
         the UDP header and UDP data. The minimum 
         length is 8 bytes because that is the length of 
         the header. The field size sets a theoretical 
         limit of 65,535 bytes (8 byte header + 65,527 
         bytes of data) for a UDP datagram. However the 
         actual limit for the data length, which is 
         imposed by the underlying IPv4 protocol, is 
         65,507 bytes (65,535 minus 8 byte UDP header 
         minus 20 byte IP header).
         
         In IPv6 jumbograms it is possible to have 
         UDP packets of size greater than 65,535 bytes. 
         RFC 2675 specifies that the length field is set 
         to zero if the length of the UDP header plus 
         UDP data is greater than 65,535.";
    }
  }
  
  grouping icmp-header {
    description
      "Collection of ICMP header fields that can be 
       used to setup a match filter.";
    
    leaf type {
      type uint8;
      description
        "Also known as Control messages.";
      reference "RFC 792";
    }
    
    leaf code {
      type uint8;
      description
        "ICMP subtype. Also known as Control messages.";
    }
    
    leaf rest-of-header {
      type uint32;
      description
        "Four-bytes field, contents vary based on the 
         ICMP type and code.";
    }
  }
}
